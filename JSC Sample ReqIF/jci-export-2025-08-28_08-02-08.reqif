# Jama Connect by Jama Software

# Specification: Original
- Global ID: GID-CMP-98985
- Name: Original
- ID: JSCI3-CMP-1

## JSCI3-SET-5: Copy Paste Images (Set)
- Global ID: GID-SET-98876

### JSCI3-TXT-19: CP1 (Text)
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- Global ID: GID-TXT-98996

### JSCI3-TXT-22: CP2 (Text)
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- Global ID: GID-TXT-99005

### JSCI3-TXT-25: CP3 (Text)
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- Global ID: GID-TXT-99014

### JSCI3-TXT-28: CP4 (Text)
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- Global ID: GID-TXT-99023

### JSCI3-TXT-30: CP5 (Text)
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- Global ID: GID-TXT-99028

### JSCI3-TXT-32: CP6 (Text)
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- Global ID: GID-TXT-99156

## JSCI3-SET-6: Attached Images (Set)
- Global ID: GID-SET-98882

### JSCI3-TXT-20: A1 (Text)
- Global ID: GID-TXT-98997

### JSCI3-TXT-23: A2 (Text)
- Global ID: GID-TXT-99006

### JSCI3-TXT-26: A3 (Text)
- Global ID: GID-TXT-99015

### JSCI3-TXT-29: A4 (Text)
- Global ID: GID-TXT-99024

### JSCI3-TXT-31: A5 (Text)
- Global ID: GID-TXT-99029

### JSCI3-TXT-33: A6 (Text)
- Global ID: GID-TXT-99157

## JSCI3-SET-7: Both Type (Set)
- Global ID: GID-SET-98891

### JSCI3-TXT-21: BT1 (Text)
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- Global ID: GID-TXT-99000

### JSCI3-TXT-24: BT2 (Text)
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- Global ID: GID-TXT-99009

### JSCI3-TXT-27: BT3 (Text)
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- Global ID: GID-TXT-99018
